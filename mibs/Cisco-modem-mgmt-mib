--------------------------------------------------------------------
-- CISCO-MODEM-MGMT-MIB.my:  Cisco Modem Mgmt MIB file
--
-- January 1996, Viet Nguyen
--
-- Copyright (c) 1996 by cisco Systems, Inc.
-- All rights reserved.
--
--------------------------------------------------------------------
-- Revision 3.2  1996/06/06 08:18:18  jturner
-- CSCdi59698:  New platform commit: AS5200
-- Bienvenidos a Brasil!
--
-- Revision 3.1  1996/01/25  00:53:07  vnguyen
-- placeholder file
--
--------------------------------------------------------------------

CISCO-MODEM-MGMT-MIB DEFINITIONS ::= BEGIN

IMPORTS
        MODULE-IDENTITY,
        OBJECT-TYPE,
        Integer32,
        Gauge32,
        Counter32,
        TimeTicks
                FROM SNMPv2-SMI
        MODULE-COMPLIANCE,
        OBJECT-GROUP
                FROM SNMPv2-CONF
        TruthValue,
		   DisplayString
               FROM SNMPv2-TC
        InterfaceIndex
               FROM IF-MIB
        ciscoMgmt
              FROM CISCO-SMI
          Unsigned32
              FROM CISCO-TC;

ciscoModemMgmtMIB MODULE-IDENTITY
        LAST-UPDATED    "9601111000Z"
        ORGANIZATION    "Cisco Systems, Inc."
        CONTACT-INFO
                "       Cisco Systems
                        Customer Service

                Postal: 170 W Tasman Drive
                        San Jose, CA  95134
                        USA

                   Tel: +1 800 553-NETS

                E-mail: cs-snmp@cisco.com"
        DESCRIPTION
                ""
        REVISION        "9601110000z"
        DESCRIPTION
                "Initial version of this MIB module."
        ::= { ciscoMgmt 47 }

ciscoModemMgmtMIBObjects OBJECT IDENTIFIER ::= { ciscoModemMgmtMIB 1 }

cmSystemInfo     OBJECT IDENTIFIER ::= { ciscoModemMgmtMIBObjects 1 }
cmGroupInfo      OBJECT IDENTIFIER ::= { ciscoModemMgmtMIBObjects 2 }
cmLineInfo       OBJECT IDENTIFIER ::= { ciscoModemMgmtMIBObjects 3 }

--
--  System Wide Modem Info Table
--

cmSystemInstalledModem OBJECT-TYPE
       SYNTAX     Gauge32
       UNITS      "modems"
       MAX-ACCESS read-only
       STATUS     current
       DESCRIPTION
               "The actual number of modems that are currently installed
                within this system."
       ::= { cmSystemInfo 1 }

cmSystemConfiguredGroup OBJECT-TYPE
       SYNTAX     Gauge32
       MAX-ACCESS read-only
       STATUS     current
       DESCRIPTION
               "The actual number of modem groups that are currently
                configured within this system.  Maximum value for this
                object is cmSystemInstalledModem."
       ::= { cmSystemInfo 2 }

cmSystemWatchdogTime OBJECT-TYPE
       SYNTAX     Integer32
       UNITS      "minutes"
       MAX-ACCESS read-write
       STATUS     current
       DESCRIPTION
               "A passive software watchdog timer value will be used to
                recover a modem which enters into an unexpected state and
                hangs. When this watch dog timer times out, the modem
                associated Call Processing state will be set back to IDLE,
                all related TDM paths will be restored to default
                configurations, and all of call processing related actions
                will stop for the modem."
       DEFVAL { 3 }
       ::= { cmSystemInfo 3 }

cmSystemStatusPollTime OBJECT-TYPE
       SYNTAX     Integer32 (2..60)
       UNITS      "seconds"
       MAX-ACCESS read-write
       STATUS     current
       DESCRIPTION
               "The ideal time interval between modem status polling via the
                out of band management port."
       DEFVAL { 5 }
       ::= { cmSystemInfo 4 }

cmSystemMaxRetries OBJECT-TYPE
       SYNTAX     Integer32 (0..10)
       MAX-ACCESS read-write
       STATUS     current
       DESCRIPTION
               "A reply event is expected to be received for every message
                sent to the modem through the out of band management port.
                If an expected reply event is not received, the message will
                be sent to the modem again. This object specifies the maximum
                number of retries that should be executed."
       DEFVAL { 3 }
       ::= { cmSystemInfo 5 }

--
--  Modem Group General Info Table
--

cmGroupTable OBJECT-TYPE
        SYNTAX     SEQUENCE OF CmGroupEntry
        MAX-ACCESS not-accessible
        STATUS     current
        DESCRIPTION
                "Table of descriptive and status information about the groups
                 of modems."
        ::= { cmGroupInfo 1 }

cmGroupEntry OBJECT-TYPE
        SYNTAX     CmGroupEntry
        MAX-ACCESS not-accessible
        STATUS     current
        DESCRIPTION
                "An entry in the table, containing information about a single
                 group of modems."
        INDEX { cmGroupIndex }
        ::= { cmGroupTable 1 }

CmGroupEntry ::=
        SEQUENCE {
            cmGroupIndex                    Unsigned32,
            cmGroupTotalDevices             Integer32
        }

cmGroupIndex OBJECT-TYPE
        SYNTAX     Unsigned32
        MAX-ACCESS not-accessible
        STATUS     current
        DESCRIPTION
                "This object identifies the group containing the modems for
                 which this entry contains information."
        ::= { cmGroupEntry 1 }

cmGroupTotalDevices OBJECT-TYPE
        SYNTAX      Integer32
        MAX-ACCESS  read-only
        STATUS      current
        DESCRIPTION
                "The total number of modem devices which are configured in
                 the group."
        ::= { cmGroupEntry 2 }

--
-- Table for Modem Group Members
--

cmGroupMemberTable OBJECT-TYPE
        SYNTAX     SEQUENCE OF CmGroupMemberEntry
        MAX-ACCESS not-accessible
        STATUS     current
        DESCRIPTION
                "Table of information about the modem members in modem groups."
        ::= { cmGroupInfo 2 }

cmGroupMemberEntry OBJECT-TYPE
        SYNTAX     CmGroupMemberEntry
        MAX-ACCESS not-accessible
        STATUS     current
        DESCRIPTION
                "An entry in the table, containing information about modem
                 members in a group.  The modem groups are currently created
                 when an associated Async interface groups are configured
                 via CLI command 'interface group-async' and not via SNMP."
        INDEX {
                cmGroupIndex,
                cmSlotIndex,
                cmPortIndex
              }
        ::= { cmGroupMemberTable 1 }

CmGroupMemberEntry ::=
        SEQUENCE {
            cmSlotIndex                    Unsigned32,
            cmPortIndex                    Unsigned32
        }

cmSlotIndex OBJECT-TYPE
        SYNTAX     Unsigned32
        MAX-ACCESS not-accessible
        STATUS     current
        DESCRIPTION
               "The modem feature card slot number in the group."
        ::= { cmGroupMemberEntry  1 }

cmPortIndex OBJECT-TYPE
        SYNTAX     Unsigned32
        MAX-ACCESS read-only
        STATUS     current
        DESCRIPTION
               "The modem port number of a modem feature card in the group."
        ::= { cmGroupMemberEntry 2 }

--
--  Modem Line Status Info Table
--

cmLineStatusTable OBJECT-TYPE
       SYNTAX     SEQUENCE OF CmLineStatusEntry
       MAX-ACCESS not-accessible
       STATUS     current
       DESCRIPTION
               "A collection of objects that describe the status of the modem."
       ::= { cmLineInfo 1 }

cmLineStatusEntry OBJECT-TYPE
       SYNTAX     CmLineStatusEntry
       MAX-ACCESS not-accessible
       STATUS     current
       DESCRIPTION
               "An entry in the table, containing status information about a
                single modem."
       INDEX { cmSlotIndex, cmPortIndex }
       ::= { cmLineStatusTable 1 }

CmLineStatusEntry ::=
       SEQUENCE {
           cmInterface                       InterfaceIndex,
           cmGroup                           Integer32,
           cmManufacturerID                  DisplayString,
           cmProductDetails                  DisplayString,
           cmManageable                      TruthValue,
           cmState                           INTEGER,
           cmCallDirection                   INTEGER,
           cmDisconnectReason                INTEGER,
           cmCallDuration                    TimeTicks,
           cmCallPhoneNumber                 DisplayString,
           cmCallerID                        DisplayString,
           cmModulationSchemeUsed            INTEGER,
           cmProtocolUsed                    INTEGER,
           cmTXRate                          Gauge32,
           cmRXRate                          Gauge32,
           cmTXAnalogSignalLevel             Integer32,
           cmRXAnalogSignalLevel             Integer32
       }

cmInterface OBJECT-TYPE
       SYNTAX     InterfaceIndex
       MAX-ACCESS read-only
       STATUS     current
       DESCRIPTION
               "The interface that this modem is connected."
       ::= { cmLineStatusEntry 1 }

cmGroup OBJECT-TYPE
       SYNTAX     Integer32
       MAX-ACCESS read-only
       STATUS     current
       DESCRIPTION
               "The modem group number that the modem may be in."
       ::= { cmLineStatusEntry 2 }

cmManufacturerID OBJECT-TYPE
       SYNTAX     DisplayString (SIZE (0..79))
       MAX-ACCESS read-only
       STATUS     current
       DESCRIPTION
               "A textual description to identify the modem, including the
                manufacturer's name and type of modem."
       ::= { cmLineStatusEntry 3 }

cmProductDetails OBJECT-TYPE
       SYNTAX     DisplayString (SIZE (0..79))
       MAX-ACCESS read-only
       STATUS     current
       DESCRIPTION
               "A textual description of the modem, including hardware revision
                number, firmware revision number, feature set and optionally,
                its serial number."
       ::= { cmLineStatusEntry 4 }

cmManageable OBJECT-TYPE
       SYNTAX     TruthValue
       MAX-ACCESS read-only
       STATUS     current
       DESCRIPTION
               "The Manageable modem allows to be accessed through the out of
                band management port in which the modem statistic data can be
                retrieved, and the Direct Connect session can be used to
                provide the test and debugging ability. This object specifies
                whether this modem is a Manageable modem."
       ::= { cmLineStatusEntry 5 }

cmState OBJECT-TYPE
       SYNTAX     INTEGER {
                        unknown(1),
                        onHook(2),
                        offHook(3),  -- and not connected
                        connected(4),
                        busiedOut(5),
                        disabled(6),
                        bad(7),
                        loopback(8),
                        downloadFirmware(9),
                        downloadFirmwareFailed(10)
                  }
       MAX-ACCESS read-only
       STATUS     current
       DESCRIPTION
               "Indicates the current state of modem.  The meaning of each
                state code is explained below:

                    unknown: the current state of the modem is unknown.

                    onHook: the condition similar to hanging up a telephone
                    receiver.  The call cannot enter a connected state when
                    the modem is onHook.

                    offHook: The condition similar to picking up a telephone
                    receiver to dial or answer a call.

                    connected: The modem is in a state when it can transmit or
                    receive data over the communications line.

                    busiedOut: The modem is busied out (i.e. taken out of
                    service) and cannot make outgoing calls or receive incoming
                    calls.

                    disabled: The modem is in a reset state and non-functional.
                    This state can be set and clear via cmHoldReset.

                    bad: The modem is suspected or proven to be bad.  The
                    operator can take the modem out of service and mark
                    the modem as 'bad' via cmBad.

                    loopback: The modem is in a state where it is currently
                    running back-to-back loopback testing.

                    downloadFirmware: The modem is in a state where it is
                    currently downloading the firmware.

                    downloadFirmwareFailed: The modem is not operational because
                    the downloading of firmware to it has failed."
       ::= { cmLineStatusEntry 6 }

cmCallDirection OBJECT-TYPE
       SYNTAX     INTEGER {
                        incoming(1),
                        outgoing(2),
                        none(3)
                  }
       MAX-ACCESS read-only
       STATUS     current
       DESCRIPTION
               "The modem can be used either as an incoming call or
                outgoing call. This object specifies the direction of
                the current or previous call."
       ::= { cmLineStatusEntry 7 }

cmDisconnectReason OBJECT-TYPE
       SYNTAX     INTEGER {
                        unknown(1),
                        lostCarrier(2),
                        noCarrier(3),
                        noDialTone(4),
                        busy(5),
                        modemWatchdogTimeout(6),
                        dtrDrop(7),
                        userHangup(8),
                        compressionProblem(9),
                        retrainFailure(10),
                        remoteLinkDisconnect(11),
                        abort(12),
                        inactivityTimeout(13),
                        dialStringError(14),
                        linkFailure(15),
                        modulationError(16),
                        dialTimeout(17),
                        remoteHangup(18)
                   }
       MAX-ACCESS read-only
       STATUS     current
       DESCRIPTION
               "Indicates the reason that the last connection or call attempt
                disconnected.  The meaning of each reason code is explained
                below:

                    unknown: the failure reason is unknown or there has been
                    no previous call.

                    lostCarrier: the call was disconnected because the loss
                    of carrier.

                    noCarrier: the dial out attempt has failed because the
                    modem detects no carrier.

                    noDialTone: the dial out attempt has failed because the
                    modem failed to detect a dial tone.

                    busy: the call attempt failed because the modem detected
                    a busy signal.

                    modemWatchdogTimeout: the modem internal watchdog timer
                    has expired.

                    dtrDrop: DTR has been turned off while the modem is to
                    disconnect on DTR drop.

                    userHangup: normal disconnect where the user hangs up call.

                    compressionProblem: the call is disconnected due to a
                    problem detected during compression in the modem.

                    retrainFailure: the modem did not successfully train and
                    reach data mode on the previous connections.

                    remoteLinkDisconnect: the remote link disconnected the
                    connection.

                    abort: the call was aborted.

                    inactivityTimeout: the modem automatically hangs up because
                    data is not sent or received within the inactivity time out.

                    dialStringError: the dialed phone number is invalid.

                    linkFailure: the modem detects a link failure.

                    modulationError: the modem detects a modulation error.

                    dialTimeout: the modem times out while attempting to dial.

                    remoteHangup: the remote side hangs up the connection."
       ::= { cmLineStatusEntry 8 }

cmCallDuration OBJECT-TYPE
       SYNTAX     TimeTicks
       MAX-ACCESS read-only
       STATUS     current
       DESCRIPTION
               "This object specifies the call duration of the current
                or previous call."
       ::= { cmLineStatusEntry 9 }

cmCallPhoneNumber OBJECT-TYPE
       SYNTAX     DisplayString (SIZE (0..64))
       MAX-ACCESS read-only
       STATUS     current
       DESCRIPTION
               "The dialed outgoing telephone number of the current or
                previous call."
       ::= { cmLineStatusEntry 10 }

cmCallerID OBJECT-TYPE
       SYNTAX     DisplayString (SIZE (0..64))
       MAX-ACCESS read-only
       STATUS     current
       DESCRIPTION
               "The incoming caller identification of the current or
                previous call."
       ::= { cmLineStatusEntry 11 }

cmModulationSchemeUsed OBJECT-TYPE
       SYNTAX     INTEGER {
                        unknown(1),
                        bell103a(2),
                        bell212a(3),
                        v21(4),
                        v22(5),
                        v22bis(6),
                        v32(7),
                        v32bis(8),
                        vfc(9),
                        v34(10)
                  }
       MAX-ACCESS read-only
       STATUS     current
       DESCRIPTION
               "The modem modulation scheme used in the current or previous
                call.  This object exists only for modems which have
                cmManageable to be true."
       ::= { cmLineStatusEntry 12 }

cmProtocolUsed OBJECT-TYPE
       SYNTAX     INTEGER {
                        normal(1),
                        direct(2),
                        reliableMNP(3),
                        reliableLAPM(4)
                  }
       MAX-ACCESS read-only
       STATUS     current
       DESCRIPTION
               "The modem protocol used in the current or previous call.
                This object exists only for modems which have cmManageable
                to be true."
       ::= { cmLineStatusEntry 13 }

cmTXRate OBJECT-TYPE
       SYNTAX     Gauge32
       UNITS      "bits/second"
       MAX-ACCESS read-only
       STATUS     current
       DESCRIPTION
               "The speed of modem transmit rate of the current or previous
                call in bits per second.  This object exists only for modems
                which have cmManageable to be true."
       ::= { cmLineStatusEntry 14 }

cmRXRate OBJECT-TYPE
       SYNTAX     Gauge32
       UNITS      "bits/second"
       MAX-ACCESS read-only
       STATUS     current
       DESCRIPTION
               "The speed of modem receive rate of the current or previous
                call in bits per second.  This object exists only for modems
                which have cmManageable to be true."
       ::= { cmLineStatusEntry 15 }

cmTXAnalogSignalLevel OBJECT-TYPE
       SYNTAX     Integer32 (0 | -43..-9)
       UNITS      "dBm"
       MAX-ACCESS read-only
       STATUS     current
       DESCRIPTION
               "The modem transmit analog signal level in the current or
                previous call.  The unit used is in dBm.  This object exists
                only for modems which have cmManageable to be true."
       ::= { cmLineStatusEntry 16 }

cmRXAnalogSignalLevel OBJECT-TYPE
       SYNTAX     Integer32 (0 | -43..-9)
       UNITS      "dBm"
       MAX-ACCESS read-only
       STATUS     current
       DESCRIPTION
               "The modem receive analog signal level in the current or
                previous call.  The unit used is in dBm.  This object exists
                only for modems which have cmManageable to be true."
       ::= { cmLineStatusEntry 17 }

--
--  Modem Line Configuration Table
--

cmLineConfigTable OBJECT-TYPE
       SYNTAX     SEQUENCE OF CmLineConfigEntry
       MAX-ACCESS not-accessible
       STATUS     current
       DESCRIPTION
               "A collection of objects that describe some of the configuration
                info of the modem."
       ::= { cmLineInfo 2 }

cmLineConfigEntry OBJECT-TYPE
       SYNTAX     CmLineConfigEntry
       MAX-ACCESS not-accessible
       STATUS     current
       DESCRIPTION
               "An entry in the table, containing configuration information
                about a single modem."
       AUGMENTS { cmLineStatusEntry }
       ::= { cmLineConfigTable 1 }

CmLineConfigEntry ::=
       SEQUENCE {
           cmATModePermit                    TruthValue,
           cmStatusPolling                   TruthValue,
           cmBusyOutRequest                  TruthValue,
           cmShutdown                        TruthValue,
           cmHoldReset                       TruthValue,
           cmBad                             TruthValue
       }

cmATModePermit OBJECT-TYPE
       SYNTAX     TruthValue
       MAX-ACCESS read-write
       STATUS     current
       DESCRIPTION
               "Direct Connect session is used for test and debugging purpose
                by using the modem AT commands through the out of band
                management port when cmManageable is true.

                This object specifies whether the Direct Connect session is
                permitted to be used at this modem.

                If cmManageable is true(1), Direct Connect session via the out
                of band port is allowed and false(2) indicates that it isn't
                allowed for the modem."
       DEFVAL { true }
       ::= { cmLineConfigEntry 1 }

cmStatusPolling OBJECT-TYPE
       SYNTAX     TruthValue
       MAX-ACCESS read-write
       STATUS     current
       DESCRIPTION
               "Modem status and events can be polled through the out of band
                management port when the cmManageable is true.

                This object specifies whether this status polling feature is
                enabled at this modem.

                If cmManageable is true(1), status polling will occur for the
                modem and false(2) indicates that no status polling will occur."
       DEFVAL { true }
       ::= { cmLineConfigEntry 2 }

cmBusyOutRequest OBJECT-TYPE
       SYNTAX     TruthValue
       MAX-ACCESS read-write
       STATUS     current
       DESCRIPTION
               "This object is used to put modem out of service, i.e. modem
                cannot make calls or answer calls. If the modem to
                be busyout is handling a call, the busyout action will
                be taken after the current call is disconnected. After
                modem is busyout, the following commands can be applied
                to those modems - reset, bad modem, download modem firmware,
                etc. This is called nice or graceful busyout.

                The value of true(1) indicates the busyOut request has been
                issued to the modem, but the busyout could be pending. The
                management entity needs to query the cmState to see
                if the modem is successfully busied out. The value of false(2)
                indicates the modem is not given the busyOut command."
       DEFVAL { false }
       ::= { cmLineConfigEntry 3 }

cmShutdown OBJECT-TYPE
       SYNTAX     TruthValue
       MAX-ACCESS read-write
       STATUS     current
       DESCRIPTION
               "This object is used to put modem out of service, i.e. modem
                cannot make calls or answer calls. This is a hard busyout
                command to bring the modem out of service immediately without
                waiting for the call to be ended normally.  After modem is
                shutdown, the following commands can be applied to those
                modems - reset, bad modem, download modem firmware, etc.

                The value of true(1) indicates the hard busyout has been
                issued to the modem.  The value of false(2) indicates the
                modem has not been hard busyout."
       DEFVAL { false }
       ::= { cmLineConfigEntry 4 }

cmHoldReset OBJECT-TYPE
       SYNTAX     TruthValue
       MAX-ACCESS read-write
       STATUS     current
       DESCRIPTION
               "A command hold-reset will put the state of modem into reset mode
                until an inverse command to bring modem out of RESET mode.
                During the period of reset mode, this modem can not be used
                and is non-functional.

                This object is only valid when cmState is onHook, busiedOut, or
                disabled.  The value of true(1) attempts to put the modem in
                reset mode, and the value of false(2) takes the modem out of
                reset."
       DEFVAL { false }
       ::= { cmLineConfigEntry 5 }

cmBad OBJECT-TYPE
       SYNTAX     TruthValue
       MAX-ACCESS read-write
       STATUS     current
       DESCRIPTION
               "This object can hold modem out of service and marks the modem
                as suspected or proven to be bad. During the router start-up
                initialization sequence, modem back-to-back tests will test
                modems and mark those modems failing tests as bad modems.  The
                management entity also can use this command to lock out the
                suspicious modem or unlock the modem to do further debugging
                or test. This command will be used accompanied with cmholdReset
                command to put modem out of service.  This command doesn't do
                the reset. For a normally good modem, it can start handling
                calls after it exits from modem reset mode. For a bad modem, it
                cannot start handling calls after it exits from modem reset
                mode. The manager needs to take modem out of bad modem mode
                in order to handle calls.

                This object is only valid when cmState is onHook or
                busiedOut. The value of true(1) indicates the modem is
                suspected to be bad and its state is set to bad.  The
                value of false(2) indicates the modem has not been suspected
                to be bad or has been re-marked as good."
       DEFVAL { false }
       ::= { cmLineConfigEntry 6 }

--
--  Modem Line Statistics Table
--

cmLineStatisticsTable OBJECT-TYPE
       SYNTAX     SEQUENCE OF CmLineStatisticsEntry
       MAX-ACCESS not-accessible
       STATUS     current
       DESCRIPTION
               "A collection of objects that describe the status of the modem."
       ::= { cmLineInfo 3 }

cmLineStatisticsEntry OBJECT-TYPE
       SYNTAX     CmLineStatisticsEntry
       MAX-ACCESS not-accessible
       STATUS     current
       DESCRIPTION
               "An entry in the table, containing status information about a
                single modem."
       AUGMENTS { cmLineStatusEntry }
       ::= { cmLineStatisticsTable 1 }

CmLineStatisticsEntry ::=
       SEQUENCE {
           cmRingNoAnswers                   Counter32,
           cmIncomingConnectionFailures      Counter32,
           cmIncomingConnectionCompletions   Counter32,
           cmOutgoingConnectionFailures      Counter32,
           cmOutgoingConnectionCompletions   Counter32,
           cmFailedDialAttempts              Counter32,
           cmNoDialTones                     Counter32,
           cmDialTimeouts                    Counter32,
           cmWatchdogTimeouts                Counter32,
           cm2400OrLessConnections           Counter32,
           cm2400To14400Connections          Counter32,
           cmGreaterThan14400Connections     Counter32,
           cmNoCarriers                      Counter32,
           cmLinkFailures                    Counter32,
           cmProtocolErrors                  Counter32,
           cmPollingTimeouts                 Counter32
       }

cmRingNoAnswers OBJECT-TYPE
       SYNTAX     Counter32
       UNITS      "calls"
       MAX-ACCESS read-only
       STATUS     current
       DESCRIPTION
               "A counter to count the calls that ringing was detected but
                the call was not answered at this modem."
       ::= { cmLineStatisticsEntry 1 }

cmIncomingConnectionFailures OBJECT-TYPE
       SYNTAX     Counter32
       UNITS      "calls"
       MAX-ACCESS read-only
       STATUS     current
       DESCRIPTION
               "A counter to count the number of incoming connection requests
                that this modem answered in which it could not train with the
                other DCE.  This object exists only for modems which have
                cmManageable to be true."
       ::= { cmLineStatisticsEntry 2 }

cmIncomingConnectionCompletions OBJECT-TYPE
       SYNTAX     Counter32
       UNITS      "calls"
       MAX-ACCESS read-only
       STATUS     current
       DESCRIPTION
               "A counter to count the number of incoming connection requests
                that this modem answered and successfully trained with the
                other DCE.  This object exists only for modems which have
                cmManageable to be true."
       ::= { cmLineStatisticsEntry 3 }

cmOutgoingConnectionFailures OBJECT-TYPE
       SYNTAX     Counter32
       UNITS      "calls"
       MAX-ACCESS read-only
       STATUS     current
       DESCRIPTION
               "A counter to count the number of outgoing calls from this modem
                which successfully went off hook and dialed, in which it could
                not train with the other DCE.  This object exists only for
                modems which have cmManageable to be true."
       ::= { cmLineStatisticsEntry 4 }

cmOutgoingConnectionCompletions OBJECT-TYPE
       SYNTAX     Counter32
       UNITS      "calls"
       MAX-ACCESS read-only
       STATUS     current
       DESCRIPTION
               "A counter to count the number of outgoing calls from this modem
                which resulted in successfully training with the other DCE.
                This object exists only for modems which have cmManageable to
                be true."
       ::= { cmLineStatisticsEntry 5 }

cmFailedDialAttempts OBJECT-TYPE
       SYNTAX     Counter32
       UNITS      "calls"
       MAX-ACCESS read-only
       STATUS     current
       DESCRIPTION
               "A counter to count the number of call attempts that failed
                because the modem didn't go off hook, or there was no dial
                tone."
       ::= { cmLineStatisticsEntry 6 }

cmNoDialTones OBJECT-TYPE
       SYNTAX     Counter32
       UNITS      "calls"
       MAX-ACCESS read-only
       STATUS     current
       DESCRIPTION
               "A counter to count the number of times the dial tone expected
                but not received.  This object exists only for modems which
                have cmManageable to be true."
       ::= { cmLineStatisticsEntry 7 }

cmDialTimeouts OBJECT-TYPE
       SYNTAX     Counter32
       UNITS      "calls"
       MAX-ACCESS read-only
       STATUS     current
       DESCRIPTION
               "A counter to count the number of times the dial time-out
                occurred.  This object exists only for modems which have
                cmManageable to be true."
       ::= { cmLineStatisticsEntry 8 }

cmWatchdogTimeouts OBJECT-TYPE
       SYNTAX     Counter32
       UNITS      "calls"
       MAX-ACCESS read-only
       STATUS     current
       DESCRIPTION
               "The number of times the Call Processing watchdog timer has
                expired."
       ::= { cmLineStatisticsEntry 9 }

cm2400OrLessConnections OBJECT-TYPE
       SYNTAX     Counter32
       UNITS      "calls"
       MAX-ACCESS read-only
       STATUS     current
       DESCRIPTION
               "The number of connections initially established at a modulation
                speed of 2400 bits per second or less.  This object exists only
                for modems which have cmManageable to be true."
       ::= { cmLineStatisticsEntry 10 }

cm2400To14400Connections OBJECT-TYPE
       SYNTAX     Counter32
       UNITS      "calls"
       MAX-ACCESS read-only
       STATUS     current
       DESCRIPTION
               "The number of connections initially established at a modulation
                speed of greater than 2400 bits per second and less than 14400
                bits per second.  This object exists only for modems which have
                cmManageable to be true."
       ::= { cmLineStatisticsEntry 11 }

cmGreaterThan14400Connections OBJECT-TYPE
       SYNTAX     Counter32
       UNITS      "calls"
       MAX-ACCESS read-only
       STATUS     current
       DESCRIPTION
               "The number of connections initially established at a modulation
                speed of greater than 14400 bits per second.  This object exists
                only for modems which have cmManageable to be true."

       ::= { cmLineStatisticsEntry 12 }

cmNoCarriers OBJECT-TYPE
       SYNTAX     Counter32
       UNITS      "calls"
       MAX-ACCESS read-only
       STATUS     current
       DESCRIPTION
               "A counter to count the number of times that the disconnect
                reason is no carrier.  This object exists only for modems which
                have cmManageable to be true."
       ::= { cmLineStatisticsEntry 13 }

cmLinkFailures OBJECT-TYPE
       SYNTAX     Counter32
       UNITS      "calls"
       MAX-ACCESS read-only
       STATUS     current
       DESCRIPTION
               "A counter to count the number of times that the disconnect
                reason is link failure.  This object exists only for modems
                which have cmManageable to be true."
       ::= { cmLineStatisticsEntry 14 }

cmProtocolErrors OBJECT-TYPE
       SYNTAX     Counter32
       UNITS      "errors"
       MAX-ACCESS read-only
       STATUS     current
       DESCRIPTION
               "A counter to count the number of times that the out of band
                protocol error occurred.  This object exists only for modems
                which have cmManageable to be true."
       ::= { cmLineStatisticsEntry 15 }

cmPollingTimeouts OBJECT-TYPE
       SYNTAX     Counter32
       UNITS      "errors"
       MAX-ACCESS read-only
       STATUS     current
       DESCRIPTION
               "A counter to count the number of times that the out of band
                protocol time-out error occurred.  This object exists only for
                modems which have cmManageable to be true."
       ::= { cmLineStatisticsEntry 16 }

--
-- conformance information
--

ciscoModemMgmtMIBConformance OBJECT IDENTIFIER ::= { ciscoModemMgmtMIB 3 }
ciscoModemMgmtMIBCompliances OBJECT IDENTIFIER ::=
                                        { ciscoModemMgmtMIBConformance 1 }
ciscoModemMgmtMIBGroups      OBJECT IDENTIFIER ::=
                                        { ciscoModemMgmtMIBConformance 2 }


-- compliance statements

ciscoModemMgmtMIBCompliance MODULE-COMPLIANCE
        STATUS  current
        DESCRIPTION
                "The compliance statement for entities which implement
                 the cisco Modem Management MIB"
        MODULE  -- this module
                MANDATORY-GROUPS {
                        cmSystemInfoGroup,
                        cmLineInfoGroup,
                        cmGroupInfoGroup
                }
                GROUP cmManagedLineInfoGroup
                DESCRIPTION
                        "This group is mandatory for all managed modems."
        ::= { ciscoModemMgmtMIBCompliances 1 }

-- units of conformance

cmSystemInfoGroup OBJECT-GROUP
        OBJECTS {
            cmSystemInstalledModem,
            cmSystemConfiguredGroup,
            cmSystemWatchdogTime,
            cmSystemStatusPollTime,
            cmSystemMaxRetries
        }
        STATUS  current
        DESCRIPTION
                "A collection of objects providing system configuration and
                 status information."
        ::= { ciscoModemMgmtMIBGroups 1 }

cmGroupInfoGroup OBJECT-GROUP
        OBJECTS {
            -- modem group info
            cmGroupTotalDevices,
            -- modem group members info
            cmPortIndex
        }
        STATUS  current
        DESCRIPTION
                "A collection of objects providing modem configuration and
                 statistics information for modem groups."
        ::= { ciscoModemMgmtMIBGroups 2 }

cmLineInfoGroup OBJECT-GROUP
        OBJECTS {
            -- status
            cmInterface,
            cmGroup,
            cmManufacturerID,
            cmProductDetails,
            cmManageable,
            cmState,
            cmDisconnectReason,
            cmCallDirection,
            cmCallDuration,
            cmCallPhoneNumber,
            cmCallerID,
            -- configurations
            cmATModePermit,
            cmStatusPolling,
            cmBusyOutRequest,
            cmShutdown,
            cmHoldReset,
            cmBad,
            -- statistics
            cmRingNoAnswers,
            cmFailedDialAttempts,
            cmWatchdogTimeouts
        }
        STATUS  current
        DESCRIPTION
                "A collection of objects providing modem configuration and
                 statistics information for individual modem."
        ::= { ciscoModemMgmtMIBGroups 3 }

cmManagedLineInfoGroup OBJECT-GROUP
        OBJECTS {
            cmModulationSchemeUsed,
            cmProtocolUsed,
            cmTXRate,
            cmRXRate,
            cmTXAnalogSignalLevel,
            cmRXAnalogSignalLevel,
            cmIncomingConnectionFailures,
            cmIncomingConnectionCompletions,
            cmOutgoingConnectionFailures,
            cmOutgoingConnectionCompletions,
            cmNoDialTones,
            cmDialTimeouts,
            cm2400OrLessConnections,
            cm2400To14400Connections,
            cmGreaterThan14400Connections,
            cmNoCarriers,
            cmLinkFailures,
            cmProtocolErrors,
            cmPollingTimeouts
        }
        STATUS current
        DESCRIPTION
                "A collection of objects providing modem configuration and
                 statistics information for individual managed modems."
        ::= { ciscoModemMgmtMIBGroups 4 }

END
