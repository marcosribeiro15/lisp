-- File Name : AGENT-SAMPLE-MIB
-- Date      : Thu Feb 22 18:33:22 GMT+06:30 2001
-- Author    : AdventNet Agent Toolkit - MibEditor 4.1
-- File Name : AGENT-SAMPLE-MIB
-- Date      : Thu May 04 17:24:54 GMT+06:30 2000
-- Author    : AdventNet Agent Toolkit - MibEditor 4.0
-- 
-- AGENT-SAMPLE-MIB       module definition
-- 
-- The       definitions in this module illustrate the use of different 
-- command       clauses available with the Advent Extensible agent, to 
-- instrument       data collection for the MIB objects. 
-- 
-- This       file is tailored to be used on a Windows95/NT platform 
-- because      of the use of some system commands)
-- 
-- Ver       1.0
AGENT-SAMPLE-MIB	DEFINITIONS ::= BEGIN
	IMPORTS
		enterprises, OBJECT-TYPE, NOTIFICATION-TYPE
			FROM SNMPv2-SMI
		TEXTUAL-CONVENTION, DisplayString
			FROM SNMPv2-TC
		DisplayString
			FROM RFC1213-MIB;

-- TEXTUAL-CONVENTIONS --
	RowStatus ::= TEXTUAL-CONVENTION 
		DISPLAY-HINT	""
		STATUS			current
		DESCRIPTION		""
		SYNTAX 			INTEGER  { active ( 1 ) , notInService ( 2 ) , notReady ( 3 ) , createAndGo ( 4 ) , createAndWait ( 5 ) , destroy ( 6 ) } 

	org	OBJECT IDENTIFIER
		::=  {  iso  3  }

	dod	OBJECT IDENTIFIER
		::=  {  org  6  }

	internet	OBJECT IDENTIFIER
		::=  {  dod  1  }

	mgmt	OBJECT IDENTIFIER
		::=  {  internet  2  }

	private	OBJECT IDENTIFIER
		::=  {  internet  4  }

	mib-2	OBJECT IDENTIFIER
		::=  {  mgmt  1  }

	enterprises	OBJECT IDENTIFIER
		::=  {  private  1  }

	adventnet	OBJECT IDENTIFIER
		::=  {  enterprises  2162  }

	products	OBJECT IDENTIFIER
		::=  {  adventnet  1  }

	events	OBJECT IDENTIFIER
		::=  {  adventnet  2  }

	experimental	OBJECT IDENTIFIER
		::=  {  adventnet  3  }

	demo	OBJECT IDENTIFIER
		::=  {  adventnet  4  }

	webNMS	OBJECT IDENTIFIER
		::=  {  products  1  }

	agent	OBJECT IDENTIFIER
		::=  {  products  2  }

	agentSystem	OBJECT IDENTIFIER
		::=  {  demo  1  }

	agentDisk	OBJECT IDENTIFIER
		::=  {  demo  2  }

	aapplications	OBJECT IDENTIFIER
		::=  {  demo  3  }

	aroute	OBJECT IDENTIFIER
		::=  {  demo  4  }

	utilities	OBJECT IDENTIFIER
		::=  {  demo  6  }

	notifications	OBJECT IDENTIFIER
		::=  {  demo  7  }

	tftpModule	OBJECT IDENTIFIER
		::=  {  agent  2  }

	agentDescr	OBJECT-TYPE	
		SYNTAX			DisplayString
		MAX-ACCESS		read-write
		STATUS			current
		DESCRIPTION		
				"Description of the agent"
		::=  {  agentSystem  1  }

	agentSupportContact	OBJECT-TYPE	
		SYNTAX			DisplayString
		MAX-ACCESS		read-write
		STATUS			current
		DESCRIPTION		
				"Support information for the Agent"
		::=  {  agentSystem  3  }

	agentLocation	OBJECT-TYPE	
		SYNTAX			DisplayString
		MAX-ACCESS		read-write
		STATUS			current
		DESCRIPTION		
				"Location information for the Agent"
		::=  {  agentSystem  4  }

	agentAvailMemory	OBJECT-TYPE	
		SYNTAX			DisplayString
		MAX-ACCESS		read-write
		STATUS			current
		DESCRIPTION		
				"Currently available memory"
		::=  {  agentSystem  5  }

	agentPlatformName	OBJECT-TYPE	
		SYNTAX			DisplayString  ( SIZE ( 0 .. 255  ) ) 
		MAX-ACCESS		read-only
		STATUS			current
		DESCRIPTION		
				"Gives you the agent Platform"
		REFERENCE		"The uname command ."
		::=  {  agentSystem  6  }

	adiskTable	OBJECT-TYPE
		SYNTAX		SEQUENCE  OF  AdiskEntry
		MAX-ACCESS	not-accessible
		STATUS		current
		DESCRIPTION	
			"User statistics of disk in table form"
		REFERENCE
		" Just for test..."
		::=  { agentDisk  1 }

	adiskEntry	OBJECT-TYPE
		SYNTAX		AdiskEntry
		MAX-ACCESS	not-accessible
		STATUS		current
		DESCRIPTION	
			"The entry for the adiskTable."
		REFERENCE		" Just for test..."
		INDEX		{  adiskID  }
		::=  { adiskTable 1 }

	AdiskEntry  ::=  SEQUENCE {
		adiskID  Integer32,
		adiskName  DisplayString,
		adiskCapacity  Integer32,
		adiskUsed  Integer32,
		adiskFree  Integer32
		}


	adiskID	OBJECT-TYPE	
		SYNTAX			Integer32
		MAX-ACCESS		read-only
		STATUS			current
		DESCRIPTION		
				"A Disk's unique ID"
		REFERENCE		" Just for test..."
		::=  {  adiskEntry  1  }


	adiskName	OBJECT-TYPE	
		SYNTAX			DisplayString
		MAX-ACCESS		read-write
		STATUS			current
		DESCRIPTION		
				"Name of the Disk"
		REFERENCE		" Just for test..."
		::=  {  adiskEntry  2  }


	adiskCapacity	OBJECT-TYPE	
		SYNTAX			Integer32
		MAX-ACCESS		read-write
		STATUS			current
		DESCRIPTION		
				"Capacity of the Disk"
		::=  {  adiskEntry  3  }


	adiskUsed	OBJECT-TYPE	
		SYNTAX			Integer32
		MAX-ACCESS		read-write
		STATUS			current
		DESCRIPTION		
				"Amount of disk space used"
		::=  {  adiskEntry  4  }


	adiskFree	OBJECT-TYPE	
		SYNTAX			Integer32
		MAX-ACCESS		read-write
		STATUS			current
		DESCRIPTION		
				"Amout of disk space free"
		::=  {  adiskEntry  5  }

	aaplicationTable	OBJECT-TYPE
		SYNTAX		SEQUENCE  OF  AaplicationEntry
		MAX-ACCESS	not-accessible
		STATUS		current
		DESCRIPTION	
			"This table contains the applications information."

		::=  { aapplications  1 }

	aaplicationEntry	OBJECT-TYPE
		SYNTAX		AaplicationEntry
		MAX-ACCESS	not-accessible
		STATUS		current
		INDEX		{  aaplicationID  }
		::=  { aaplicationTable 1 }

	AaplicationEntry  ::=  SEQUENCE {
		aaplicationID  Integer32,
		aaplicationName  DisplayString,
		aaplicationVersion  DisplayString,
		aaplicationInstallDate  DisplayString,
		aaplicationTablestatus  RowStatus
		}


	aaplicationID	OBJECT-TYPE	
		SYNTAX			Integer32
		MAX-ACCESS		read-write
		STATUS			current
		DESCRIPTION		
				"The applications Unique Id."
		::=  {  aaplicationEntry  1  }


	aaplicationName	OBJECT-TYPE	
		SYNTAX			DisplayString
		MAX-ACCESS		read-write
		STATUS			current
		DESCRIPTION		
				"The Name of Application."
		::=  {  aaplicationEntry  2  }


	aaplicationVersion	OBJECT-TYPE	
		SYNTAX			DisplayString
		MAX-ACCESS		read-write
		STATUS			current
		DESCRIPTION		
				"The version of the application used"
		::=  {  aaplicationEntry  3  }


	aaplicationInstallDate	OBJECT-TYPE	
		SYNTAX			DisplayString
		MAX-ACCESS		read-write
		STATUS			current
		DESCRIPTION		
				"The Install date of the application."
		::=  {  aaplicationEntry  4  }


	aaplicationTablestatus	OBJECT-TYPE	
		SYNTAX			RowStatus
		MAX-ACCESS		read-write
		STATUS			current
		DESCRIPTION		
				"Operational status of the application"
		::=  {  aaplicationEntry  5  }

	aaplicationUserTable	OBJECT-TYPE
		SYNTAX		SEQUENCE  OF  AaplicationUserEntry
		MAX-ACCESS	not-accessible
		STATUS		current
		DESCRIPTION	
			"The table for the user's application"
		::=  { aapplications  2 }

	aaplicationUserEntry	OBJECT-TYPE
		SYNTAX		AaplicationUserEntry
		MAX-ACCESS	not-accessible
		STATUS		current
		DESCRIPTION	
			"An Entry of an user application based on application Table"
		INDEX		{  aaplicationID, aaplicationUserId  }
		::=  { aaplicationUserTable 1 }

	AaplicationUserEntry  ::=  SEQUENCE {
		aaplicationUserId  Integer32,
		aaplicationUserName  DisplayString,
		aaplicationUserTableStatus  RowStatus
		}


	aaplicationUserId	OBJECT-TYPE	
		SYNTAX			Integer32
		MAX-ACCESS		read-only
		STATUS			current
		DESCRIPTION		
				"The Unique Id of an user application"
		::=  {  aaplicationUserEntry  1  }


	aaplicationUserName	OBJECT-TYPE	
		SYNTAX			DisplayString  ( SIZE ( 0 .. 255  ) ) 
		MAX-ACCESS		read-write
		STATUS			current
		DESCRIPTION		
				"The name of the User Application"
		::=  {  aaplicationUserEntry  2  }


	aaplicationUserTableStatus	OBJECT-TYPE	
		SYNTAX			RowStatus  { active ( 1 ) , notInService ( 2 ) , notReady ( 3 ) , createAndGo ( 4 ) , createAndWait ( 5 ) , destroy ( 6 ) } 
		MAX-ACCESS		read-write
		STATUS			current
		DESCRIPTION		
				"Operational status of the user application"
		::=  {  aaplicationUserEntry  3  }

	agentDate	OBJECT-TYPE	
		SYNTAX			DisplayString
		MAX-ACCESS		read-only
		STATUS			current
		DESCRIPTION		
				"Get local date."
		::=  {  utilities  1  }

	agentNetstat	OBJECT-TYPE	
		SYNTAX			DisplayString
		MAX-ACCESS		read-write
		STATUS			current
		DESCRIPTION		
				"Gives the netstat command result"
		REFERENCE		"Check with OS "
		::=  {  utilities  2  }

	agentPing	OBJECT-TYPE	
		SYNTAX			DisplayString
		MAX-ACCESS		read-write
		STATUS			current
		DESCRIPTION		
				"Ping a specified host with given flags"
		REFERENCE		"For flags refer man page "
		::=  {  utilities  3  }

	scalarNotifications	NOTIFICATION-TYPE
		OBJECTS			{ agentNetstat ,agentLocation ,agentAvailMemory ,agentPing  }
		STATUS			current
		DESCRIPTION		
				"Description"
		::=  {  notifications  1  }

	tableNotifications	NOTIFICATION-TYPE
		OBJECTS			{ adiskName ,aaplicationUserName ,adiskUsed  }
		STATUS			current
		DESCRIPTION		
				"Description"
		::=  {  notifications  2  }

	tftpServerName	OBJECT-TYPE	
		SYNTAX			DisplayString
		MAX-ACCESS		read-write
		STATUS			current
		DESCRIPTION		
				"The TFTP Server name ."
		DEFVAL			{ "localhost" }
		::=  {  tftpModule  1  }

	tftpSourceFileName	OBJECT-TYPE	
		SYNTAX			DisplayString
		MAX-ACCESS		read-write
		STATUS			current
		DESCRIPTION		
				"The source file name to be TFTPed."
		DEFVAL			{ "autoexec.bat" }
		::=  {  tftpModule  2  }

	tftpDestFileName	OBJECT-TYPE	
		SYNTAX			DisplayString
		MAX-ACCESS		read-write
		STATUS			current
		DESCRIPTION		
				"The destination file name of the TFTP"
		DEFVAL			{ "destFile.txt" }
		::=  {  tftpModule  3  }

	tftpRequest	OBJECT-TYPE	
		SYNTAX			INTEGER  { get ( 1 ) , put ( 2 ) } 
		MAX-ACCESS		read-write
		STATUS			current
		DESCRIPTION		
				"The type of TFTP request"
		::=  {  tftpModule  4  }

END
